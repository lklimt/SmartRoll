# -*- coding: utf-8 -*-
# ============================================================
# SMARTROLL / SR-MEC-001 - Rev.E9
# Dvoudilny magneticky unasec pro roletovou hridel
# FreeCAD 1.1
#
# REV.E9 - KOREKCE PROFILU HRIDELE + M3 MATICE
#
# SCHVALENE ROZMERY HRIDELE:
# - rozmer hridele pres protilehle plochy = 17.00 mm
# - montazni vule otvoru = 0.20 mm
# - vnitrni osmihran pouzdra = 17.20 mm AF
# - svlak: sirka 7.00 mm
# - svlak: svetlost/vyska 2.50 mm
# - montazni vule svlaku = 0.20 mm
#
# HLAVNI ROZMERY:
# - upinaci cast = 6.00 mm
# - magneticky limec = 5.00 mm
# - celkem = 11.00 mm
# - OD = 26.00 mm
# - kruhova svetlost magneticke casti = Ø21.00 mm
#
# KONSTRUKCE:
# - dve skutecne poloviny objimky
# - montaz kolem jiz nainstalovane hridele
# - delici rovina Y=0
# - 2x protilehly M3 spoj na X=+/-13.10 mm
# - 2x radialni magnet 4x2 mm, 180 deg
# - svlakovy vyrez na +X plose osmihranu
#
# M3 MATICE:
# - kapsa je pristupna z vnejsi strany dolni poloviny
# - matice se vklada z vnejsi strany, bez nutnosti zasouvat ji pres otvor pro sroub
# - kapsa je zvetsena proti jmenovitemu AF 5.50 mm na 5.80 mm
# - hloubka kapsy 2.80 mm
# - zachovano lokalni zesileni kolem M3 oka
#
# POZNAMKA:
# 7.00 mm se zde NEPOUZIVA jako rozmer hridele pres plochy.
# Primarni rozmer hridele je 17.00 mm AF.
# ============================================================

import FreeCAD as App
import FreeCADGui as Gui
import Part
import math

DOC_NAME = "SR-MEC-001_RevE9"

# ---------------- HRIDEL ----------------
SHAFT_AF = 17.00
SHAFT_CLEARANCE = 0.20
INNER_AF = SHAFT_AF + SHAFT_CLEARANCE

# Svlak na +X plose.
SVLAK_W = 7.00
SVLAK_H = 2.50
SVLAK_CLEARANCE = 0.20

# ---------------- HLAVNI ROZMERY ----------------
CLAMP_W = 6.00
COLLAR_W = 5.00
TOTAL_W = 11.00
OD = 26.00
ROTATION_BORE = 21.00

# ---------------- M3 SPOJE ----------------
EAR_OUTER_D = 6.80
EAR_BORE_D = 3.30
EAR_RING_W = 2.40
EAR_RADIAL_LEN = 4.20
EAR_CENTER_X = 13.10
EAR_CENTER_Z = TOTAL_W / 2.0

HEAD_D = 6.00
HEAD_DEPTH = 1.20

# Matice M3 - realne vlozeni z vnejsi strany.
NUT_AF = 5.80
NUT_DEPTH = 2.80
NUT_CLEARANCE = 0.15
NUT_POCKET_AF = NUT_AF + NUT_CLEARANCE

# ---------------- MAGNETY ----------------
MAG_D = 4.00
MAG_LEN = 2.00
MAG_POCKET_D = 4.20
MAG_POCKET_DEPTH = 2.15
MAG_ANGLES = (90.0, 270.0)


def V(x, y, z=0):
    return App.Vector(float(x), float(y), float(z))


def cyl(d, h, z=0):
    s = Part.makeCylinder(d / 2.0, h)
    s.translate(V(0, 0, z))
    return s


def oct_prism_af(af, h, z=0):
    """Regular octagonal prism defined by across-flats dimension."""
    r = (af / 2.0) / math.cos(math.radians(22.5))
    p = []
    for i in range(8):
        a = math.radians(22.5 + i * 45.0)
        p.append(V(r * math.cos(a), r * math.sin(a), z))
    p.append(p[0])
    return Part.Face(Part.makePolygon(p)).extrude(V(0, 0, h))


def hex_prism_af(af, depth, y0, x, z):
    """Hexagonal prism, AF-defined, extruded along Y."""
    r = af / math.sqrt(3.0)
    pts = []
    for i in range(6):
        a = math.radians(30.0 + i * 60.0)
        pts.append(V(x + r * math.cos(a), y0, z + r * math.sin(a)))
    pts.append(pts[0])
    return Part.Face(Part.makePolygon(pts)).extrude(V(0, depth, 0))


def radial_pocket(d, depth, ang, r, z):
    a = math.radians(ang)
    start = V(r * math.cos(a), r * math.sin(a), z)
    return Part.makeCylinder(
        d / 2.0,
        depth,
        start,
        V(-math.cos(a), -math.sin(a), 0)
    )


def make_ear(x, y0):
    outer = Part.makeCylinder(
        EAR_OUTER_D / 2.0,
        EAR_RING_W,
        V(x, y0, EAR_CENTER_Z),
        V(0, 1, 0)
    )
    inner = Part.makeCylinder(
        EAR_BORE_D / 2.0,
        EAR_RING_W + 0.10,
        V(x, y0 - 0.05, EAR_CENTER_Z),
        V(0, 1, 0)
    )
    return outer.cut(inner)


def make_bridge(x, y0):
    length = EAR_RADIAL_LEN
    if x > 0:
        bx = OD / 2.0 - 0.10
    else:
        bx = -OD / 2.0 + 0.10 - length

    b = Part.makeBox(length, EAR_RING_W, EAR_RING_W)
    b.translate(V(bx, y0, EAR_CENTER_Z - EAR_RING_W / 2.0))
    return b


# ============================================================
# NOVY DOKUMENT
# ============================================================
try:
    App.closeDocument(DOC_NAME)
except:
    pass

doc = App.newDocument(DOC_NAME)

# ============================================================
# 1. ZAKLADNI TELESO
# ============================================================
body = cyl(OD, TOTAL_W)

# Upinaci cast 0-6 mm: otvor je definovan primo rozmerem 17.20 AF.
body = body.cut(
    oct_prism_af(INNER_AF, CLAMP_W + 0.04, -0.02)
)

# Magneticky limec 6-11 mm: kruhova svetlost Ø21.
body = body.cut(
    cyl(ROTATION_BORE, COLLAR_W + 0.04, CLAMP_W - 0.02)
)

# ============================================================
# 2. VYREZ PRO SVLAK
# ============================================================
svlak_width = SVLAK_W + SVLAK_CLEARANCE
svlak_depth = SVLAK_H + SVLAK_CLEARANCE

# Pro AF=17.20 lezi vnitrni +X plocha na x=8.60 mm.
svlak_x0 = INNER_AF / 2.0 - 0.02

svlak_cut = Part.makeBox(
    svlak_depth + 0.20,
    svlak_width,
    CLAMP_W + 0.04
)
svlak_cut.translate(
    V(svlak_x0, -svlak_width / 2.0, -0.02)
)
body = body.cut(svlak_cut)

# ============================================================
# 3. DVE POLOVINY
# ============================================================
half_box_pos = Part.makeBox(40.0, 20.0, TOTAL_W + 2.0)
half_box_pos.translate(V(-20.0, 0.0, -1.0))

half_box_neg = Part.makeBox(40.0, 20.0, TOTAL_W + 2.0)
half_box_neg.translate(V(-20.0, -20.0, -1.0))

half_pos = body.common(half_box_pos)
half_neg = body.common(half_box_neg)

# ============================================================
# 4. M3 SPOJE
# ============================================================
for x in (EAR_CENTER_X, -EAR_CENTER_X):
    upper_ear = make_ear(x, 0.0)
    lower_ear = make_ear(x, -EAR_RING_W)

    upper_bridge = make_bridge(x, 0.0)
    lower_bridge = make_bridge(x, -EAR_RING_W)

    half_pos = half_pos.fuse(upper_ear).fuse(upper_bridge)
    half_neg = half_neg.fuse(lower_ear).fuse(lower_bridge)

for x in (EAR_CENTER_X, -EAR_CENTER_X):
    # Prubezny otvor M3.
    through_lower = Part.makeCylinder(
        EAR_BORE_D / 2.0,
        EAR_RING_W + 0.30,
        V(x, -EAR_RING_W - 0.05, EAR_CENTER_Z),
        V(0, 1, 0)
    )
    half_neg = half_neg.cut(through_lower)

    through_upper = Part.makeCylinder(
        EAR_BORE_D / 2.0,
        EAR_RING_W + 0.30,
        V(x, -0.05, EAR_CENTER_Z),
        V(0, 1, 0)
    )
    half_pos = half_pos.cut(through_upper)

    # Horni kapsa pro hlavu M3.
    head = Part.makeCylinder(
        HEAD_D / 2.0,
        HEAD_DEPTH + 0.05,
        V(x, EAR_RING_W - HEAD_DEPTH, EAR_CENTER_Z),
        V(0, 1, 0)
    )
    half_pos = half_pos.cut(head)

    # --------------------------------------------------------
    # DOLNI MATICE - otevrena kapsa z vnejsi strany.
    # Matice se vklada z vnejsi strany Y=-2.4.
    # Misto je AF 5.95 mm, tj. 5.80 + 0.15 mm vule.
    # --------------------------------------------------------
    nutpocket = hex_prism_af(
        NUT_POCKET_AF,
        NUT_DEPTH,
        -EAR_RING_W - 0.05,
        x,
        EAR_CENTER_Z
    )
    half_neg = half_neg.cut(nutpocket)

# ============================================================
# 5. MAGNETY 180 DEG
# ============================================================
r_outer = OD / 2.0 + 0.01
zmag = CLAMP_W + COLLAR_W / 2.0

for ang in MAG_ANGLES:
    pocket = radial_pocket(
        MAG_POCKET_D,
        MAG_POCKET_DEPTH,
        ang,
        r_outer,
        zmag
    )

    if ang == 90.0:
        half_pos = half_pos.cut(pocket)
    else:
        half_neg = half_neg.cut(pocket)

# ============================================================
# 6. OBJEKTY POLOVIN
# ============================================================
objA = doc.addObject("PartDesign::Feature", "SR_MEC_001_HALF_A")
objA.Label = "SR-MEC-001 Rev.E9 - polovina A (+Y)"
objA.Shape = half_pos

objB = doc.addObject("PartDesign::Feature", "SR_MEC_001_HALF_B")
objB.Label = "SR-MEC-001 Rev.E9 - polovina B (-Y)"
objB.Shape = half_neg

# ============================================================
# 7. PARAMETRY V OBJEKTECH
# ============================================================
for obj, side_name in ((objA, "HALF_A"), (objB, "HALF_B")):
    obj.addProperty("App::PropertyString", "Revision", "Dokumentace")
    obj.Revision = "Rev.E9"

    obj.addProperty("App::PropertyString", "PartName", "Dokumentace")
    obj.PartName = side_name

    obj.addProperty("App::PropertyLength", "ShaftAcrossFlats", "Parametry")
    obj.ShaftAcrossFlats = SHAFT_AF

    obj.addProperty("App::PropertyLength", "InnerAcrossFlats", "Parametry")
    obj.InnerAcrossFlats = INNER_AF

    obj.addProperty("App::PropertyLength", "ShaftClearance", "Parametry")
    obj.ShaftClearance = SHAFT_CLEARANCE

    obj.addProperty("App::PropertyLength", "SvlakWidth", "Parametry")
    obj.SvlakWidth = SVLAK_W

    obj.addProperty("App::PropertyLength", "SvlakHeight", "Parametry")
    obj.SvlakHeight = SVLAK_H

    obj.addProperty("App::PropertyLength", "SvlakClearance", "Parametry")
    obj.SvlakClearance = SVLAK_CLEARANCE

    obj.addProperty("App::PropertyLength", "OuterDiameter", "Parametry")
    obj.OuterDiameter = OD

    obj.addProperty("App::PropertyLength", "ClampWidth", "Parametry")
    obj.ClampWidth = CLAMP_W

    obj.addProperty("App::PropertyLength", "CollarWidth", "Parametry")
    obj.CollarWidth = COLLAR_W

    obj.addProperty("App::PropertyLength", "TotalWidth", "Parametry")
    obj.TotalWidth = TOTAL_W

    obj.addProperty("App::PropertyLength", "RotationBore", "Parametry")
    obj.RotationBore = ROTATION_BORE

    obj.addProperty("App::PropertyLength", "M3Clearance", "Parametry")
    obj.M3Clearance = EAR_BORE_D

    obj.addProperty("App::PropertyLength", "NutPocketAF", "Parametry")
    obj.NutPocketAF = NUT_POCKET_AF

    obj.addProperty("App::PropertyLength", "NutPocketDepth", "Parametry")
    obj.NutPocketDepth = NUT_DEPTH

    obj.addProperty("App::PropertyLength", "MagnetDiameter", "Parametry")
    obj.MagnetDiameter = MAG_D

    obj.addProperty("App::PropertyLength", "MagnetLength", "Parametry")
    obj.MagnetLength = MAG_LEN

    obj.addProperty("App::PropertyStringList", "Notes", "Dokumentace")
    obj.Notes = [
        "Primarni rozmer hridele pres protilehle plochy = 17.00 mm.",
        "Vnitrni osmihran = 17.20 mm AF, tj. vule 0.20 mm.",
        "Svlak = 7.00 mm x 2.50 mm; vule 0.20 mm.",
        "Upinaci cast = 6.00 mm.",
        "Magneticky limec = 5.00 mm; celkem 11.00 mm.",
        "Vnejsi prumer = 26.00 mm; kruhova svetlost = 21.00 mm.",
        "Dve poloviny; delici rovina Y=0.",
        "Dva protilehle M3 spoje na X=+/-13.10 mm.",
        "M3 matice: kapsa otevrena z vnejsi strany, AF 5.95 mm.",
        "M3 kapsa: hloubka 2.80 mm.",
        "Magnety: 4x2 mm radialne, 180 deg."
    ]

objA.ViewObject.ShapeColor = (0.20, 0.20, 0.20)
objB.ViewObject.ShapeColor = (0.35, 0.35, 0.35)

# ============================================================
# 8. REFERENCNI HRIDEL
# ============================================================
shaft = cyl(SHAFT_AF, CLAMP_W)

# Referencni svlak 7x2.5 mm na +X.
shaft_key = Part.makeBox(
    SVLAK_W,
    SVLAK_H,
    CLAMP_W
)
shaft_key.translate(V(SHAFT_AF / 2.0, -SVLAK_W / 2.0, 0))
shaft = shaft.fuse(shaft_key)

ref = doc.addObject("PartDesign::Feature", "REFERENCE_SHAFT")
ref.Label = "REFERENCE - hridel 17 mm AF + svlak 7 x 2.5 mm"
ref.Shape = shaft
ref.addProperty("App::PropertyString", "Description", "Dokumentace")
ref.Description = "Kontrolni geometrie skutecne hridele pro overeni nasunuti unasece."
ref.addProperty("App::PropertyLength", "AcrossFlats", "Parametry")
ref.AcrossFlats = SHAFT_AF
ref.addProperty("App::PropertyLength", "SvlakWidth", "Parametry")
ref.SvlakWidth = SVLAK_W
ref.addProperty("App::PropertyLength", "SvlakHeight", "Parametry")
ref.SvlakHeight = SVLAK_H
ref.ViewObject.ShapeColor = (0.70, 0.70, 0.70)
ref.ViewObject.Transparency = 75

# ============================================================
# 9. DOC PARAMETRY
# ============================================================
doc.addObject("App::FeaturePython", "DESIGN_PARAMETERS")
p = doc.getObject("DESIGN_PARAMETERS")
p.addProperty("App::PropertyString", "Revision", "Dokumentace")
p.Revision = "SR-MEC-001 Rev.E9"
p.addProperty("App::PropertyString", "ShaftDefinition", "Dokumentace")
p.ShaftDefinition = "17.00 mm across opposite flats"
p.addProperty("App::PropertyString", "NutInsertion", "Dokumentace")
p.NutInsertion = "M3 nut inserted from outer side of lower joint"
p.addProperty("App::PropertyString", "Status", "Dokumentace")
p.Status = "PARAMETRIC MODEL - FreeCAD runtime validation required"

# ============================================================
# 10. FIT VIEW
# ============================================================
doc.recompute()
Gui.activeDocument().activeView().viewAxonometric()
Gui.activeDocument().activeView().fitAll()

doc.recompute()
